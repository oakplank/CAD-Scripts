Imports Inventor
Imports System.Windows.Forms

Sub Main()
    Dim oApp As Inventor.Application = ThisApplication
    Dim oTopAsmDoc As AssemblyDocument = oApp.ActiveDocument
    
    ' Prompt the user for Project and Title properties
    Dim titleValue As String = InputBox("Enter the name of the project for the Title property:", "Update Title")
    Dim projectValue As String = InputBox("Enter the project # for the Project property:", "Update Project")

    ' Loop through each sub-assembly in the top-level assembly
    For Each oOcc As ComponentOccurrence In oTopAsmDoc.ComponentDefinition.Occurrences
        If TypeOf oOcc.ReferencedDocumentDescriptor.ReferencedDocument Is AssemblyDocument Then
            Dim oSubAsmDoc As AssemblyDocument = DirectCast(oOcc.ReferencedDocumentDescriptor.ReferencedDocument, AssemblyDocument)

            ' Update properties for the sub-assembly
            UpdateProperties(oSubAsmDoc, titleValue, projectValue, isAssembly:=True)

            ' Each sub-assembly has a single part, so we can directly access that part and update its properties
            For Each oSubOcc As ComponentOccurrence In oSubAsmDoc.ComponentDefinition.Occurrences
                If TypeOf oSubOcc.ReferencedDocumentDescriptor.ReferencedDocument Is PartDocument Then
                    Dim oPartDoc As PartDocument = DirectCast(oSubOcc.ReferencedDocumentDescriptor.ReferencedDocument, PartDocument)
                    
                    ' Update properties for the part
                    UpdateProperties(oPartDoc, titleValue, projectValue)
                End If
            Next
        End If
    Next
    
    MessageBox.Show("Properties updated for all sub-assemblies and parts.", "iLogic", MessageBoxButtons.OK, MessageBoxIcon.Information)
End Sub

Sub UpdateProperties(ByRef oDoc As Document, ByVal titleValue As String, ByVal projectValue As String, Optional ByVal isAssembly As Boolean = False)
    Try
        Dim oPartProperties As PropertySet = oDoc.PropertySets.Item("Design Tracking Properties")
        If isAssembly Then
            oPartProperties.Item("Description").Value = "SEQ. CONTAINER"
        Else
            oPartProperties.Item("Description").Value = "SEQ. BLOCK"
        End If
        oPartProperties.Item("Project").Value = projectValue
    Catch ex As Exception
        MsgBox("Error setting Description or Project: " & ex.Message)
    End Try

    ' Update Title property
    Try
        Dim oSummaryInfo As PropertySet = oDoc.PropertySets.Item("Summary Information")
        oSummaryInfo.Item("Title").Value = titleValue
    Catch ex As Exception
        MsgBox("Error setting Title: " & ex.Message)
    End Try
	
	' Update Part Type property
	Try
    	Dim oSummaryInfo As PropertySet = oDoc.PropertySets.Item("User Defined Properties")
        oSummaryInfo.Item("Part Type").Value = "NA"
    Catch ex As Exception
        MsgBox("Error setting Part Type: " & ex.Message)
    End Try

    ' Save changes to the document
    oDoc.Save()
End Sub
